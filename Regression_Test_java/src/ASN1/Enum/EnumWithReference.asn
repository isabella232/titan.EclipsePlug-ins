--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Forstner, Matyas
--   Koppany, Csaba
--   Szabados, Kristof
--   Szabo, Janos Zoltan – initial implementation
--
--/////////////////////////////////////////////////////////////////////////////
-- Bug 560016; reported, see also EnumWithReference.asn
-- Original occurence: BER1.asn

EnumWithReference DEFINITIONS

  AUTOMATIC TAGS ::=

BEGIN
v2 INTEGER ::= 3
T4 ::= ENUMERATED {three(v2), one, zero(0), minusone(-1), two}
END
